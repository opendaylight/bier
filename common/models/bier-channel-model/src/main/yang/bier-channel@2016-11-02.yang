module bier-channel {
	namespace "urn:bier:channel";
	prefix "bier-channel";
	import ietf-inet-types {
       prefix "inet";
       revision-date "2013-07-15";
     }
  
  import ietf-bier {
        prefix bier;
    }
  import bier-common {
      prefix bier-common;
  }
	organization "zte";	
	revision 2016-11-02 {
    description "Initial revision.";
  }
  
      typedef bier-forwarding-type{
           type enumeration {
                enum "bier" {
                    value 1;
                }
                enum "bier-te" {
                    value 2;
                }
           }
  	  }

  typedef bp-assignment-strategy{
     type enumeration {
          enum "manual" {
              value 1;
          }
          enum "automatic" {
              value 2;
          }
     }
  }

  container bier-network-channel {
    list bier-channel {
      key "topology-id";
      leaf topology-id {
			  type string;
		  } 
      list channel {
        key "name";
        ordered-by user;
        uses channel;

        leaf ingress-node {
			type string;
		}
		leaf ingress-bfr-id {
		    type bier:bfr-id;
		}
		leaf src-tp {
            type string;
        }
        list egress-node {
            key "node-id";
            ordered-by user;
            leaf node-id {
              type string;
            }
            leaf egress-bfr-id {
                type bier:bfr-id;
            }
            list rcv-tp {
                leaf tp {
                    type string;
                }
            }
          }
        leaf bier-forwarding-type {
            type bier-forwarding-type;
        }
        leaf bp-assignment-strategy {
            type bp-assignment-strategy;
        }

      }
    }
  }
  
  grouping channel {
        leaf name {
          type string;
        }

        leaf src-ip {
          type inet:ip-address;
        }

        leaf dst-group {
          type inet:ip-address;
        }

        leaf domain-id {
          type bier-common:domain-id;
        }

        leaf sub-domain-id {
          type bier:sub-domain-id;
        }

        leaf source-wildcard {
          type uint8;
        }

        leaf group-wildcard {
          type uint8;
        }
  }
}
