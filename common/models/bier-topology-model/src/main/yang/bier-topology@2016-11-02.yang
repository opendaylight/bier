module bier-topology {
	namespace "urn:bier:topology";
	prefix "bier-topology";
	
  import ietf-inet-types {
       prefix "inet";
     }
  
  import ietf-mpls {
       prefix "mpls";
       revision-date 2016-07-05;
     }
  
  import ietf-bier {
        prefix bier;
    }
 
  import bier-common {
        prefix bier-common;
    }
	
	organization "zte";	
	revision 2016-11-02 {
    description "Initial revision.";
  }
  
  identity bier-encapsulation-mpls {
       base bier:bier-encapsulation;
       description
         "This identity represents MPLS encapsulation for bier.";
     }

	typedef bier-te-label-range-size{
		type uint32;
		description
			"The type for BIER-TE label range size.";
	}


  container bier-network-topology {
    list bier-topology {
      key "topology-id";
      ordered-by user;
      leaf topology-id {
			  type string;
			}   
			      
			list bier-node {
			  key "node-id";
			  ordered-by user;
			  uses bier-node;
		        }
					  		
			list bier-link {
			  key "link-id";
			  ordered-by user;
				uses bier-link;
		        }
						  
		        list bier-domain
			{
			  key "domain-id";
			  ordered-by user;
			  leaf domain-id {
			    type bier-common:domain-id;
			  }
			  list bier-sub-domain {
			    key "sub-domain-id";
			    ordered-by user;
			    leaf sub-domain-id {
			      type bier:sub-domain-id;
			    }
			  }
			}
		}
  }
  	
  grouping bier-node-params {
    list domain {
      key "domain-id";
      ordered-by user;
      leaf domain-id {
			  type bier-common:domain-id;
			}
	  uses bier:bier-global-cfg;
	  }
  }
  
  grouping bier-te-node-params {
    list te-domain {
      key "domain-id";
      ordered-by user;
      leaf domain-id {
			  type bier-common:domain-id;
			}
	    list te-sub-domain{
          key "sub-domain-id";
          ordered-by user;
          leaf sub-domain-id{
              type bier:sub-domain-id;
          }
          
          list te-bsl{
              key "bitstringlength";
              ordered-by user;
              leaf bitstringlength {
                type bier:bsl;
              }
          
          
              list te-si {
                key "si";
                ordered-by user;
                leaf si{
                  type bier:si;
                }
                leaf ft-label {
                    type mpls:mpls-label;
                } 
          
                 list te-bp {
                   key "tp-id";
                   ordered-by user;
                   leaf tp-id {
			               type string;
		               }
            
                   leaf bitposition {
                     //type bier-te:bit-string;
                     type uint16;
                   }
                 }
             }
          }
        
      }
	  }
  }

	grouping termination-point {
		leaf tp-id {
			type string;
		}
		leaf if-name {
		  type string;
		}
		leaf tp-ip-prefix {
			type inet:ip-address;
		}
		leaf tp-index {
			type uint32;
		}
		leaf if-speed {
		  type uint64;
		}
	}
  
  grouping bier-node {
		leaf node-id {
			type string;
		}
		leaf name {
			type string;
		}
		leaf router-id {
			type string;
		}
		container bier-node-params {
		    uses bier-node-params;
		}
		container bier-te-node-params {
		    uses bier-te-node-params;
		}
		leaf latitude {
			default 0;
			type uint64;
		}
		leaf longitude {
			default 0;
			type uint64;
		}
		list bier-termination-point {
		    key "tp-id";
		    ordered-by user;
		    uses termination-point;
		}

		container bier-te-lable-range {
			leaf label-base{
			  type mpls:mpls-label;
			}
			leaf label-range-size{
			  type bier-te-label-range-size;
			}
		}
	}
	
	grouping bier-link {
		leaf link-id {
			type string;
		}
		container link-source {
		  leaf source-node {
			  type string;
		  }
		  leaf source-tp {
			  type string;
		  }
		}
		container link-dest {
		  leaf dest-node {
			  type string;
		  }
		  leaf dest-tp {
			  type string;
		  }
		}
		leaf delay {
			default 0;
			type uint64;
		}
		leaf loss {
			default 0;
			type uint64;
		}
		leaf metric {
			type uint64;
		}
	}
	
}
