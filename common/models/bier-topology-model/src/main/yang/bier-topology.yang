module bier-topology {
	namespace "urn:bier:topology";
	prefix "bier-topology";
	
  import ietf-inet-types {
       prefix "inet";
     }
  
  import ietf-mpls {
       prefix "mpls";
     }
  
  import ietf-bier {
        prefix bier;
    }
 
  import bier-common {
        prefix bier-common;
    }
	
	organization "zte";	
	revision 2016-11-02 {
    description "Initial revision.";
  }
  
  identity bier-encapsulation-mpls {
       base bier:bier-encapsulation;
       description
         "This identity represents MPLS encapsulation for bier.";
     }
  
  container bier-network-topology {
    list bier-topology {
      key "topology-id";
      ordered-by user;
      leaf topology-id {
			  type string;
			}   
			      
			list bier-node {
			  key "node-id";
			  ordered-by user;
			  uses bier-node;
		        }
					  		
			list bier-link {
			  key "link-id";
			  ordered-by user;
				uses bier-link;
		        }
						  
		        list bier-domain
			{
			  key "domain-id";
			  ordered-by user;
			  leaf domain-id {
			    type bier-common:domain-id;
			  }
			  list bier-sub-domain {
			    key "sub-domain-id";
			    ordered-by user;
			    leaf sub-domain-id {
			      type bier:sub-domain-id;
			    }
			  }
			}
		}
  }
  	
  grouping bier-node-params {
    list domain {
      key "domain-id";
      ordered-by user;
      leaf domain-id {
			  type bier-common:domain-id;
			}
	  uses bier:bier-global-cfg;
	  }
  }
  
  
  grouping bier-node {
		leaf node-id {
			type string;
		}
		leaf name {
			type string;
		}
		leaf router-id {
			type string;
		}
		container bier-node-params {
		    uses bier-node-params;
		}
		leaf latitude {
			default 0;
			type uint64;
		}
		leaf longitude {
			default 0;
			type uint64;
		}
		list bier-termination-point {
		    key "tp-id";
		    ordered-by user;
				leaf tp-id {
					type string;
				}
		}
	}
	
	grouping bier-link {
		leaf link-id {
			type string;
		}
		container link-source {
		  leaf source-node {
			  type string;
		  }
		  leaf source-tp {
			  type string;
		  }
		}
		container link-dest {
		  leaf dest-node {
			  type string;
		  }
		  leaf dest-tp {
			  type string;
		  }
		}
		leaf bfr-adj-id {
			type uint16;
		}
		leaf delay {
			default 0;
			type uint64;
		}
		leaf loss {
			default 0;
			type uint64;
		}
	}
	
}
