module ietf-connectionless-oam {
    yang-version 1.1;
    namespace "urn:ietf:params:xml:ns:yang:ietf-connectionless-oam";
    prefix coam;

    import ietf-yang-schema-mount {
     prefix yangmnt;
     revision-date 2017-06-16;
    }
    import ietf-network-ex {
      prefix nd;
      revision-date 2017-06-30;
    }
    import ietf-yang-types {
      prefix yang;
      revision-date 2013-07-15;
    }
    import ietf-interfaces {
      prefix if;
      revision-date 2014-05-08;
    }
    import ietf-inet-types {
      prefix inet;
      revision-date 2013-07-15;
    }
    import ietf-network-instance-ex {
      prefix ni;
      revision-date 2017-07-03;
    }

    organization
      "IETF LIME Working Group";
    contact
      "Deepak Kumar dekumar@cisco.com
       Qin Wu bill.wu@huawei.com
       S Raghavan srihari@cisco.com
       Zitao Wang wangzitao@huawei.com
       R Rahman rrahman@cisco.com";
    description
      "This YANG module defines the generic configuration,
       data model, statistics for connectionless OAM to be
       used within IETF in a protocol indpendent manner.
       Functional level abstraction is indendent with
       YANG modeling. It is assumed that each protocol maps
       corresponding abstracts to its native format.
       Each protocol may extend the YANG model defined
       here to include protocol specific extensions";

    revision 2017-06-09 {
      description
        " Base model for Connectionless
         Operations, Administration,
         and Maintenance(OAM) ";
      reference
        " RFC XXXX: Connectionless
         Operations, Administration, and
         Maintenance(OAM)YANG Data Model";
    }

    feature connection-less {
      description
        "This feature indicates that OAM solution is connection less.";
    }

    feature continuity-check {
      description
        "This feature indicates that the server supports
         executing continuity check OAM command and
         returning a response. Servers that do not advertise
         this feature will not support executing
         continuity check command or rpc model for
         continuity check command.";
    }

    feature path-discovery {
      description
        "This feature indicates that the server supports
         executing path discovery OAM command and
         returning a response. Servers that do not advertise
         this feature will not support executing
         path discovery command or rpc model for
         path discovery command.";
    }

    typedef router-id {
      type yang:dotted-quad;
      description
        "A 32-bit number in the dotted quad format assigned to each
         router. This number uniquely identifies the router within an
         Autonomous System.";
    }

    typedef routing-instance-ref {
      type leafref {
        path "/ni:network-instances-ex/ni:network-instance-ex/ni:name";
      }
      description
        "This type is used for leafs that reference a routing instance
         configuration.";
    }

    typedef ipv4-multicast-group-address {
      type string {
        pattern "(2((2[4-9])|(3[0-9]))\\.)"+"
  (([0-9]|[1-9][0-9]|1[0-9][0-9]|2[0-4][0-9]|25[0-5])\\.)"
  +"{2}([0-9]|[1-9][0-9]|1[0-9][0-9]|2[0-4][0-9]|25[0-5])";
      }
      description
        "The ipv4-multicast-group-address type
         represents an IPv4 multicast address
         in dotted-quad notation.";
      reference "RFC4607";
    }

    typedef ipv6-multicast-group-address {
      type string {
        pattern "(((FF|ff)[0-9a-fA-F]{2}):)"
  +"([0-9a-fA-F]{0,4}:){0,5}((([0-9a-fA-F]{0,4}:)"
  +"?(:|[0-9a-fA-F]{0,4}))|(((25[0-5]|2[0-4][0-9]|"
  +"[01]?[0-9]?[0-9])\\.){3}(25[0-5]|2[0-4][0-9]|"
  +"[01]?[0-9]?[0-9])))";
        pattern "(([^:]+:){6}(([^:]+:[^:]+)|(.*\\..*)))|"
  +"((([^:]+:)*[^:]+)?::(([^:]+:)*[^:]+)?)";
      }
      description
        "The ipv6-multicast-group-address
         type represents an IPv6 address in full,
         mixed, shortened, and shortened-mixed
         notation.";
      reference
        "RFC4291 2.7.
         ietf-inet-types:ipv6-address";
    }

    typedef ip-multicast-group-address {
      type union {
        type ipv4-multicast-group-address;
        type ipv6-multicast-group-address;
      }
      description
        "The ip-multicast-group-address type
         represents an IP multicast address and
         is IP version neutral. The format of the
         textual representations implies the IP version.";
    }

    identity address-attribute-types {
      description
        "This is base identity of address
         attribute types which are ip-prefix,
         bgp, tunnel, pwe3, vpls, etc.";
    }

    typedef address-attribute-type {
      type identityref {
        base address-attribute-types;
      }
      description
        "Target address attribute type.";
    }

    identity time-resolution {
      description
        "Time interval resolution";
    }

    identity hours {
      base time-resolution;
      description
        "Time resolution in Hours";
    }

    identity minutes {
      base time-resolution;
      description
        "Time resolution in Minutes";
    }

    identity seconds {
      base time-resolution;
      description
        "Time resolution in Seconds";
    }

    identity milliseconds {
      base time-resolution;
      description
        "Time resolution in Milliseconds";
    }

    identity microseconds {
      base time-resolution;
      description
        "Time resolution in Microseconds";
    }

    identity nanoseconds {
      base time-resolution;
      description
        "Time resolution in Nanoseconds";
    }

    grouping cc-session-statistics {
      description
        "Grouping for session statistics.";
      container cc-session-statistics {
        description
          "cc session counters";
        leaf session-count {
          type uint32;
          description
            "Number of Continuity Check sessions.";
        }
        leaf session-up-count {
          type uint32;
          description
            "Number of sessions which are up.";
        }
        leaf session-down-count {
          type uint32;
          description
            "Number of sessions which are down.";
        }
        leaf session-admin-down-count {
          type uint32;
          description
            "Number of sessions which are admin-down.";
        }
      }
    }

    grouping session-packet-statistics {
      description
        "Grouping for per session packet statistics";
      container session-packet-statistics {
        description
          "Per session packet statistics.";
        leaf rx-packet-count {
          type uint32;
          description
            "Total number of received OAM packet count.";
        }
        leaf tx-packet-count {
          type uint32;
          description
            "Total number of transmitted OAM packet count.";
        }
        leaf rx-bad-packet {
          type uint32;
          description
            "Total number of received bad OAM packet.";
        }
        leaf tx-packet-failed {
          type uint32;
          description
            "Total number of send OAM packet failed.";
        }
      }
    }

    grouping cc-per-session-statistics {
      description
        "Grouping for per session statistics";
      container cc-per-session-statistics {
        description
          "per session statistics.";
        leaf create-time {
          type yang:date-and-time;
          description
            "Time and date when session is created.";
        }
        leaf last-down-time {
          type yang:date-and-time;
          description
            "Time and date last time session is down.";
        }
        leaf last-up-time {
          type yang:date-and-time;
          description
            "Time and date last time session is up.";
        }
        leaf down-count {
          type uint32;
          description
            "Total Continuity Check sessions down count.";
        }
        leaf admin-down-count {
          type uint32;
          description
            "Total Continuity Check sessions admin down count.";
        }
        uses session-packet-statistics;
      }
    }

    grouping session-error-statistics {
      description
        "Grouping for per session error statistics";
      container session-error-statistics {
        description
          "Per session error statistics.";
        leaf packet-drops-count {
          type uint32;
          description
            "Total received packet drops count.";
        }
        leaf packet-reorder-count {
          type uint32;
          description
            "Total received packet reordered count.";
        }
        leaf packets-out-of-seq-count {
          type uint32;
          description
            "Total received out of sequence count.";
        }
        leaf packets-dup-count {
          type uint32;
          description
            "Total received packet duplicates count.";
        }
      }
    }

    grouping session-delay-statistics {
      description
        "Grouping for per session delay statistics";
      container session-delay-statistics {
        description
          "Session delay summarised information.";
        leaf time-resolution-value {
          type identityref {
            base time-resolution;
          }
          description
            "Time units among choice of s,ms,ns etc.";
        }
        leaf min-delay-value {
          type uint32;
          description
            "Minimum delay value observed.";
        }
        leaf max-delay-value {
          type uint32;
          description
            "Maximum delay value observed.";
        }
        leaf average-delay-value {
          type uint32;
          description
            "Average delay value observed.";
        }
      }
    }

    grouping session-jitter-statistics {
      description
        "Grouping for per session jitter statistics";
      container session-jitter-statistics {
        description
          "Session jitter summarised information.";
        leaf time-resolution-value {
          type identityref {
            base time-resolution;
          }
          description
            "Time units among choice of s,ms,ns etc.";
        }
        leaf min-jitter-value {
          type uint32;
          description
            "Minimum jitter value observed.";
        }
        leaf max-jitter-value {
          type uint32;
          description
            "Maximum jitter value observed.";
        }
        leaf average-jitter-value {
          type uint32;
          description
            "Average jitter value observed.";
        }
      }
    }

    grouping session-path-verification-statistics {
      description
        "Grouping for per session path verification statistics";
      container session-path-verification-statistics {
        description
          "OAM per session path verification statistics.";
        leaf verified-count {
          type uint32;
          description
            "Total number of OAM packets that
             went through a path as intended.";
        }
        leaf failed-count {
          type uint32;
          description
            "Total number of OAM packets that
             went through an unintended path.";
        }
      }
    }

    grouping session-type {
      description
        "This object indicates the current session
         definition.";
      leaf session-type-enum {
        type enumeration {
          enum "proactive" {
            description
              "The current session is proactive";
          }
          enum "on-demand" {
            description
              "The current session is on-demand.";
          }
        }
        default "on-demand";
        description
          "Session type enum";
      }
    }

    identity tp-address-technology-type {
      description
        "Test point address type";
    }

    identity mac-address-type {
      base tp-address-technology-type;
      description
        "MAC address type";
    }

    identity ipv4-address-type {
      base tp-address-technology-type;
      description
        "IPv4 address type";
    }

    identity ipv6-address-type {
      base tp-address-technology-type;
      description
        "IPv6 address type";
    }

    identity tp-attribute-type {
      base tp-address-technology-type;
      description
        "Test point attribute type";
    }

    identity system-id-address-type {
      base tp-address-technology-type;
      description
        "System id address type";
    }

    identity as-number-address-type {
      base tp-address-technology-type;
      description
        "AS number address type";
    }

    identity group-ip-address-type {
      base tp-address-technology-type;
      description
        "Group IP address type";
    }

    identity route-distinguisher-address-type {
      base tp-address-technology-type;
      description
        "Route Distinguisher address type";
    }

    identity ip-prefix-address-type {
      base tp-address-technology-type;
      description
        "IP prefix address type";
    }

    identity tunnel-address-type {
      base tp-address-technology-type;
      description
        "Tunnel address type";
    }

    grouping tp-address {
      leaf tp-location-type-value {
        type identityref {
          base tp-address-technology-type;
        }

        description
          "Test point address type.";
      }
      choice tp-address {
        case mac-address {
          when "'tp-location-type-value' = 'mac-address-type'" {
            description
              "MAC address type";
          }
          leaf mac-address {
            type yang:mac-address;
            description
              "MAC Address";
          }
          description
            "MAC Address based MP Addressing.";
        }
        case ipv4-address {
          when "'tp-location-type-value' = 'ipv4-address-type'" {
            description
              "IPv4 address type";
          }
          leaf ipv4-address {
            type inet:ipv4-address;
            description
              "IPv4 Address";
          }
          description
            "IP Address based MP Addressing.";
        }
        case ipv6-address {
          when "'tp-location-type-value' = 'ipv6-address-type'" {
            description
              "IPv6 address type";
          }
          leaf ipv6-address {
            type inet:ipv6-address;
            description
              "IPv6 Address";
          }
          description
            "ipv6 Address based MP Addressing.";
        }

        case tp-attribute {
          when "'tp-location-type-value' = 'tp-attribute-type'" {
            description
              "Test point attribute type";
          }
          leaf tp-attribute-type {
            type address-attribute-type;
            description
              "Test point type.";
          }
          choice tp-attribute-value {
            description
              "Test point value.";
            case ip-prefix {
              leaf ip-prefix {
                type inet:ip-prefix;
                description
                  "IP prefix.";
              }
            }
            case bgp {
              leaf bgp {
                type inet:ip-prefix;
                description
                  "BGP Labeled Prefix ";
              }
            }
            case tunnel {
              leaf tunnel-interface {
                type uint32;
                description
                  "VPN Prefix ";
              }
            }
            case pw {
              leaf remote-pe-address {
                type inet:ip-address;
                description
                  "Remote pe address.";
              }
              leaf pw-id {
                type uint32;
                description
                  "Pseudowire ID is a non-zero 32-bit ID.";
                reference
                  "RFC 4379 :Detecting Multi-Protocol Label
                  Switched (MPLS) Data Plane Failures";
              }

            }
            case vpls {
              leaf route-distinguisher {
                type uint32;
                description
                  "Route Distinguisher is an 8 octets identifier
                  used to distinguish information about various
                  L2VPN advertised by a node.";
                reference
                  "RFC 4379 :Detecting Multi-Protocol Label
                  Switched (MPLS) Data Plane Failures";
              }
              leaf sender-ve-id {
                type uint32;
                description
                  "Sender's VE ID. The VE ID (VPLS Edge Identifier)
                   is a 2-octet identifier.";
                reference
                  "RFC 4379 :Detecting Multi-Protocol Label
                  Switched (MPLS) Data Plane Failures";
              }
              leaf receiver-ve-id {
                type uint32;
                description
                  "Receiver's VE ID.The VE ID (VPLS Edge Identifier)
                   is a 2-octet identifier.";
                reference
                  "RFC 4379 :Detecting Multi-Protocol Label
                  Switched (MPLS) Data Plane Failures";
              }
            }
            case mpls-mldp {
              choice root-address {
                description
                  "Root address choice.";
                case ip-address {
                  leaf source-address {
                    type inet:ip-address;
                    description
                      "IP address.";
                  }
                  leaf group-ip-address {
                    type ip-multicast-group-address;
                    description
                      "Group ip address.";
                  }
                }
                case vpn {
                  leaf as-number {
                    type inet:as-number;
                    description
                    "The AS number represents autonomous system
                    numbers which identify an Autonomous System.";
                  }
                }
                case global-id {
                  leaf lsp-id {
                    type string;
                    description
                      "LSP ID is an identifier of a LSP
                       within a MPLS network.";
                    reference
                    "RFC 4379 :Detecting Multi-Protocol Label
                     Switched (MPLS) Data Plane Failures";
                  }
                }
              }
            }
          }
        }
        case system-info {
          when "'tp-location-type-value' = 'system-id-address-type'" {
            description
              "System id address type";
          }
          leaf system-id {
            type router-id;
            description
              "System ID assigned to this node.";
          }
        }
        description
          "TP Addressing.";
      }
      description
        "TP Address";
    }

    grouping tp-address-vrf {
      description
        "Test point address with VRF.";
      leaf vrf {
        type routing-instance-ref;
        description
          "The vrf is used to describe the
           corresponding network instance";
      }
      uses tp-address;
    }

    grouping connectionless-oam-layers {
      list oam-layers {
        key "index";
        leaf index {
          type uint16 {
            range "0..65535";
          }
          description
            "Index";
        }
        leaf level {
          type int32 {
            range "-1..1";
          }
          default "0";
          description
            "Level 0 indicates default level,
             -1 means server and +1 means client layer.
             In relationship 0 means same layer.";
        }
        choice tp-location {
          case mac-address {
            leaf mac-address-location {
              type yang:mac-address;
              description
                "MAC Address";
            }
            description
              "MAC Address based MP Addressing.";
          }
          case ipv4-address {
            leaf ipv4-location {
              type inet:ipv4-address;
              description
                "Ipv4 Address";
            }
            description
              "IP Address based MP Addressing.";
          }
          case ipv6-location {
            leaf ipv6-address {
              type inet:ipv6-address;
              description
                "IPv6 Address";
            }
            description
              "IPv6 Address based MP Addressing.";
          }
          case group-ip-address-location {
            leaf group-ip-address-location {
              type ip-multicast-group-address;
              description
                "Group IP address location";
            }
            description
              "Group IP address";
          }
          case as-number-location {
            leaf as-number-location {
              type inet:as-number;
              description
                "AS number location";
            }
            description
              "AS number for point to multipoint OAM";
          }
          case system-id-location {
            leaf system-id-location {
              type router-id;
              description
                "System id location";
            }
            description
              "System ID";
          }
          description
            "TP location.";
        }

        description
          "List of related oam layers.
           0 means they are in same level, especially
           interworking scenarios of stitching multiple
           technology at same layer. -1 means server layer,
           for eg:- in case of Overlay and Underlay,
           Underlay is server layer for Overlay Test Point.
           +1 means client layer, for example in case of
           Service OAM and Transport OAM, Service OAM is client
           layer to Transport OAM.";
      }
      description
        "Connectionless related OAM layer";
    }

    grouping tp-technology {
      choice technology {
        default "technology-null";
        case technology-null {
          description
            "This is a placeholder when no technology is needed.";
          leaf tech-null {
            type empty;
            description
              "There is no technology define";
          }
        }
        description
          "Technology choice.";
      }
      description
        "OAM Technology";
    }

    grouping tp-tools {
      description
        "Test Point OAM Toolset.";
      container tp-tools {
        leaf continuity-check {
          type boolean;
          mandatory true;
          description
            "A flag indicating whether or not the
             continuity check function is supported.";
          reference
            "RFC 792: INTERNET CONTROL MESSAGE PROTOCOL.
             RFC 4443: Internet Control Message Protocol (ICMPv6)
             for the Internet Protocol Version 6 (IPv6) Specification.
             RFC 5880: Bidirectional Forwarding Detection.
             RFC 5881: BFD for IPv4 and IPv6.
             RFC 5883: BFD for Multihop Paths.
             RFC 5884: BFD for MPLS Label Switched Paths.
             RFC 5885: BFD for PW VCCV.
             RFC 6450: Multicast Ping Protocol.";
        }
        leaf path-discovery {
          type boolean;
          mandatory true;
          description
            "A flag indicating whether or not the
             path discovery function is supported.";
          reference
            "RFC 792: INTERNET CONTROL MESSAGE PROTOCOL.
             RFC 4443: Internet Control Message Protocol (ICMPv6)
             for the Internet Protocol Version 6 (IPv6) Specification.
             RFC 4884: Extended ICMP to Support Multi-part Message.
             RFC 5837:Extending ICMP for Interface
             and Next-Hop Identification.
             RFC 4379: LSP-PING.";
        }
        description
          "Container for test point OAM tools set.";
      }
    }

    grouping test-point-location-info {
      uses tp-technology;
      uses tp-tools;
      anydata root {
        yangmnt:mount-point "root";
        description
          "Root for models supported per
           test point";
      }
      uses connectionless-oam-layers;
      description
        "Test point Location";
    }

    grouping test-point-locations {
      description
        "Group of test point locations.";
          leaf tp-location-type-value {
        type identityref {
          base tp-address-technology-type;
        }
        description
          "Test point location type.";
      }
      choice location-type {
        case ipv4-location-type {
          when "'tp-location-type-value' = 'ipv4-address-type'" {
            description
              "When test point location type is equal to ipv4 address.";
          }
          container test-point-ipv4-location-list {
            list test-point-locations {
              key "ipv4-location";
              leaf ipv4-location {
                type inet:ipv4-address;
                description
                  "IPv4 Address.";
              }
              leaf vrf {
                type routing-instance-ref;
                description
                  "The vrf is used to describe the
                   corresponding network instance";
              }
              uses test-point-location-info;

              description
                "List of test point locations.";
            }
            description
              "Serves as top-level container
               for test point location list.";
          }
        }
        case ipv6-location-type {
          when "'tp-location-type-value' = 'ipv6-address-type'" {
            description
              "when test point location is equal to ipv6 address";
          }
          container test-point-ipv6-location-list {
            list test-point-locations {
              key "ipv6-location";
              leaf ipv6-location {
                type inet:ipv6-address;
                description
                  "IPv6 Address.";
              }
              leaf vrf {
                type routing-instance-ref;
                description
                  "The vrf is used to describe the
                   corresponding network instance";
              }
              uses test-point-location-info;

              description
                "List of test point locations.";
            }
            description
              "Serves as top-level container
               for test point location list.";
          }

        }
        case mac-location-type {
          when "'tp-location-type-value' = 'mac-address-type'" {
            description
              "when test point location type is equal to mac address.";
          }
          container test-point-mac-address-location-list {
            list test-point-locations {
              key "mac-address-location";
              leaf mac-address-location {
                type yang:mac-address;
                description
                  "MAC Address";
              }
              uses test-point-location-info;

              description
                "List of test point locations.";
            }
            description
              "Serves as top-level container
               for test point location list.";
          }
        }
        case group-ip-address-location-type {
          when "'tp-location-type-value' = 'group-ip-address-type'" {
            description
              "When test point location type is equal to
               group ip address.";
          }
          container test-point-group-ip-address-location-list {
            list test-point-locations {
              key "group-ip-address-location";
              leaf group-ip-address-location {
                type ip-multicast-group-address;
                description
                  "Group IP address.";
              }
              leaf vrf {
                type routing-instance-ref;
                description
                  "The vrf is used to describe the
                   corresponding network instance";
              }
              uses test-point-location-info;

              description
                "List of test point locations.";
            }
            description
              "Serves as top-level container for
               test point location list.";
          }
        }
        case group-as-number-location-type {
          when "'tp-location-type-value' = 'as-number-address-type'" {
            description
              "When test point location type is equal to
               as-number.";
          }
          container test-point-as-number-location-list {
            list test-point-locations {
              key "as-number-location";
              leaf as-number-location {
                type inet:as-number;
                description
                  "AS number for point to multi point OAM.";
              }
              leaf vrf {
                type routing-instance-ref;
                description
                  "The vrf is used to describe the
                   corresponding network instance";
              }
              uses test-point-location-info;

              description
                "List of test point locations.";
            }
            description
              "Serves as top-level container
               for test point location list.";
          }
        }
        case group-system-id-location-type {
          when "'tp-location-type-value' = 'system-id-address-type'" {
            description
              "When test point location is equal to
               system info.";
          }
          container test-point-system-info-location-list {
            list test-point-locations {
              key "system-id-location";
              leaf system-id-location {
                type inet:uri;
                description
                  "System Id.";
              }
              leaf vrf {
                type routing-instance-ref;
                description
                  "The vrf is used to describe the
                   corresponding network instance";
              }
              uses test-point-location-info;

              description
                "List of test point locations.";
            }
            description
              "Serves as top-level container for
               test point location list.";
          }
        }
        description
          "Choice of address types.";
      }
    }

    augment "/nd:networks/nd:network/nd:node" {
      description
        "Augment test points of connectionless oam.";
          uses test-point-locations;
    }

    grouping uint64-timestamp {
      description
        "Grouping for timestamp.";
      leaf timestamp-sec {
        type uint32;
        description
          "Absolute timestamp in seconds as per IEEE1588v2
           or seconds part in 64-bit NTP timestamp.";
      }
      leaf timestamp-nanosec {
        type uint32;
        description
          "Fractional part in nanoseconds as per IEEE1588v2
           or Fractional part in 64-bit NTP timestamp.";
      }
    }

    grouping timestamp {
      description
        "Grouping for timestamp.";
      leaf timestamp-type {
        type uint32;
        description
          "Truncated PTP = 0, NTP = 1";
      }
      uses uint64-timestamp;
    }

    grouping path-discovery-data {
      description
        "Path discovery related data output from nodes.";
      container src-test-point {
        description
          "Source test point.";
        uses tp-address-vrf;
      }
      container dest-test-point {
        description
          "Destination test point.";
        uses tp-address-vrf;
      }
      leaf sequence-number {
        type uint64;
        description
          "Sequence number in data packets.";
      }
      leaf hop-cnt {
        type uint8;
        description
          "Hop count.";
      }
      uses session-packet-statistics;
      uses session-error-statistics;
      uses session-delay-statistics;
      uses session-jitter-statistics;
      container path-verification {
        description
          "Optional path verification related information.";
        leaf flow-info {
          type string;
          description
            "Informations that refers to the flow.";
        }
        uses session-path-verification-statistics;
      }
      container path-trace-info {
        description
          "Optional path trace per-hop test point information.
           The list has typically a single element for per-hop
           cases like path-discovery RPC but allows a list of
           hop related information for other types of
           data retrieval methods.";
        list path-trace-info-list {
          key "index";
          description
            "Path trace information list.";
          leaf index {
            type uint32;
            description
              "Trace information index.";
          }
          uses tp-address-vrf;
          uses timestamp;
          leaf ingress-intf-name {
            type if:interface-ref;
            description
              "Ingress interface name";
          }
          leaf egress-intf-name {
            type if:interface-ref;
            description
              "Egress interface name";
          }
          leaf queue-depth {
            type uint32;
            description
              "Length of the egress interface
               queue of the interface.";
          }
          leaf transit-delay {
            type uint32;
            description
              "Time in nano seconds
               packet spent transiting a node.";
          }
          leaf app-meta-data {
            type uint64;
            description
              "Application specific
               data added by node.";
          }
        }
      }
    }
    grouping continuity-check-data {
      description
        "Continuity check data output from nodes.";
      container src-test-point {
        description
          "Source test point.";
        uses tp-address-vrf;
        leaf egress-intf-name {
          type if:interface-ref;
          description
            "Egress interface name";
        }
      }
      container dest-test-point {
        description
          "Destination test point.";
        uses tp-address-vrf;
        leaf ingress-intf-name {
          type if:interface-ref;
          description
            "Ingress interface name";
        }
      }
      leaf sequence-number {
        type uint64;
        description
          "Sequence number.";
      }
      leaf hop-cnt {
        type uint8;
        description
          "Hop count.";
      }
      uses session-packet-statistics;
      uses session-error-statistics;
      uses session-delay-statistics;
      uses session-jitter-statistics;
    }

    container cc-session-statistics-data {
      if-feature "continuity-check";
      config false;
      description
        "CC operational information.";
      container cc-ipv4-sessions-statistics {
        description
          "CC ipv4 sessions";
        uses cc-session-statistics;

      }
      container cc-ipv6-sessions-statistics {
        description
          "CC ipv6 sessions";
        uses cc-session-statistics;
      }
    }
  }
