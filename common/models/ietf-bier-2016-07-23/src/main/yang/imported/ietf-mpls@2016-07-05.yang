module ietf-mpls {

     namespace "urn:ietf:params:xml:ns:yang:ietf-mpls";

     prefix "mpls";

     import ietf-routing-ex {
       prefix "rt";
       revision-date 2016-10-20;
     }

     import ietf-interfaces {
       prefix "if";
       revision-date 2014-05-08;
     }

     organization "IETF MPLS Working Group";

     contact
       "WG Web:   <http://tools.ietf.org/wg/mpls/>

        WG List:  <mailto:mpls@ietf.org>

        WG Chair: Loa Andersson
                  <mailto:loa@pi.nu>

        WG Chair: Ross Callon
                  <mailto:rcallon@juniper.net>


        WG Chair: George Swallow
                  <mailto:swallow.ietf@gmail.com>

                  <mailto:tsaad@cisco.com>

        Editor:   Kamran Raza
                  <mailto:skraza@cisco.com>

        Editor:   Rakesh Gandhi
                  <mailto:rgandhi@cisco.com>

        Editor:   Xufeng Liu
                  <mailto: xufeng.liu.ietf@gmail.com>

        Editor:   Vishnu Pavan Beeram
                  <mailto:vbeeram@juniper.net>

        Editor:   Himanshu Shah
                  <mailto:hshah@ciena.com>

        Editor:   Igor Bryskin
                  <mailto: Igor.Bryskin@huawei.com>

        Editor:   Xia Chen
                  <mailto:jescia.chenxia@huawei.com>

        Editor:   Raqib Jones
                  <mailto:raqib@Brocade.com>

        Editor:   Bin Wen
                  <mailto:Bin_Wen@cable.comcast.com>";

     description
       "This YANG module defines the essential components for the
        management of the MPLS subsystem.";

     revision "2016-07-05" {
       description
         "Latest revision:
           - Addressed MPLS-RT review comments";
       reference "RFC 3031: A YANG Data Model for base MPLS";
     }

     typedef mpls-label {
       type uint32 {
         range "0..1048575";
       }


       description
         "The MPLS label range";
     }

     grouping interface-mpls {
       description "MPLS interface properties grouping";
       leaf enabled {
         type boolean;
         description
           "'true' if mpls encapsulation is enabled on the
            interface. 'false' if mpls encapsulation is enabled
            on the interface.";
       }
       leaf mtu {
         type uint32;
         description
           "MPLS Maximum Transmission Unit (MTU)";
       }
     }

     augment "/rt:routing" {
       description "MPLS augmentation.";
       container mpls {
         description
           "MPLS container, to be used as an augmentation target node
            other MPLS sub-features config, e.g. MPLS static LSP, MPLS
            LDP LSPs, and Trafic Engineering MPLS LSP Tunnels, etc.";

         list interface {
           key "name";
           description "List of MPLS interfaces";
           leaf name {
             type if:interface-ref;
             description
               "The name of a configured MPLS interface";
           }
           container config {
             description "Holds intended configuration";
             uses interface-mpls;
           }
           container state {
             config false;
             description "Holds inuse configuration";
             uses interface-mpls;
           }
         }
       }
     }


     augment "/rt:routing-state" {
       description "MPLS augmentation.";
       container mpls {
         config false;
         description
           "MPLS container, to be used as an augmentation target node
            other MPLS sub-features state";
       }
     }
   }
