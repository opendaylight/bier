module bier-pce {
    yang-version 1;
    namespace "urn:bier:pce";
    prefix "bier-pce";

    import bier-topology {prefix topo; }
    import ietf-bier {prefix bier;}

    revision "2017-03-28" {
        description "Initial revision of bier-pce model";
    }


    typedef path-type{
       type enumeration {
            enum "next-hop" {
                value 0;
            }
            enum "next-next-hop" {
                value 1;
            }
       }
    }


    grouping links {
        list path-link {
            uses topo:bier-link;
        }
    	leaf path-metric {
            type uint32;
        }
    }

    grouping path-key {
        leaf bfir-node-id {
            type string;
        }
        leaf bfer-node-id {
            type string;
        }
    }



    grouping BierPath {

         leaf bfir-node-id {
             type string;
         }
         list bfer {
             key "bfer-node-id";
             leaf bfer-node-id {
                 type string;
             }
             container bier-path {
                 uses links;
             }
         }
    }

    grouping backup-path {
        leaf destination-node {
            type string;
        }
        list path {
            uses topo:bier-link;
        }
    }
    grouping te-frr-path {
        container frr-path {
            container next-hop-path {
                uses backup-path;
            }
            list next-next-hop-path {
                uses backup-path;
            }
            list excluding-link {
                uses topo:bier-link;
            }
        }
    }

    grouping frr-key {
        container te-frr-key {
            leaf sub-domain-id {
                type bier:sub-domain-id;
            }
            container protected-link {
                uses topo:bier-link;
            }
        }
    }

    rpc create-bier-path {
        input {
            leaf sub-domain-id {
                type bier:sub-domain-id;
            }
            leaf channel-name {
                type string;
            }
            leaf bfir-node-id {
                type string;
            }
            list bfer {
                leaf bfer-node-id {
                    type string;
                }
            }
			leaf save-create-fail {
			    type boolean;
			    default true;
			}

        }

        output {
            leaf channel-name {
                    type string;
                }
            uses BierPath;
		}
	}



    rpc remove-bier-path {
        input {
            leaf channel-name {
                type string;
            }
            leaf sub-domain-id {
                type bier:sub-domain-id;
            }
            leaf bfir-node-id {
                 type string;
            }
            list bfer {
                leaf bfer-node-id {
                    type string;
                }
            }

        }
        output {
            leaf channel-name {
                type string;
            }
            uses BierPath;
        }
    }



	
    notification bier-path-update {
        description
        "Indicates that bier path is changed.";
        leaf channel-name {
            type string;
        }

        uses BierPath;
    }



    rpc query-bier-path {
        input {
            leaf channel-name {
                type string;
            }
            leaf sub-domain-id {
                type bier:sub-domain-id;
            }
            leaf bfir-node-id {
                 type string;
            }
            leaf bfer-node-id {
                type string;
            }
        }
        output {
            container bier-path {
                uses links;
            }
        }
    }

    rpc query-bier-instance-path {
        input {
            leaf channel-name {
                type string;
}
        }
        output {
            list link {
                leaf link-id {
                    type string;
                }
            }
        }
    }

    rpc query-channel-through-port {
        input {
            leaf node-id {
                type string;
            }
            leaf tp-id {
                type string;
            }

        }

        output {
            list related-channel {
                leaf channel-name {
                    type string;
                }
                leaf bfir {
                    type string;
                }
            }
		}
	}

	rpc create-te-frr-path {
    	input {
    		uses frr-key;
    	}
    	output {
    		uses te-frr-path;
    	}
    }

    rpc remove-te-frr-path {
    	input {
    		uses frr-key;
    	}
    }

    notification te-frr-path-update {
        uses frr-key;
        uses te-frr-path;
    }

    rpc query-te-frr-path {
        input {
			uses frr-key;
        }
        output {
            list link {
                leaf link-id {
                    type string;
                }
            }
        }
    }
}
