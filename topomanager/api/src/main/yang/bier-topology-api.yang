module bier-topology-api {
	namespace "urn:bier:topology:api";
	prefix "bier-topology-api";
	
  import ietf-inet-types {
       prefix "inet";
     }
  
  import ietf-bier {
        prefix bier;
    }
    
  import bier-common {
        prefix bier-common;
    }
  
  import bier-topology {
        prefix bier-topology;
    }
	
	organization "zte";	
	revision 2016-11-02 {
    description "Initial revision.";
  }
  
  identity bier-encapsulation-mpls {
       base bier:bier-encapsulation;
       description
         "This identity represents MPLS encapsulation for bier.";
     }
  
  grouping topology {
    leaf topology-id {
			type string;
		}
		list node-id {
		  leaf node-id {
				type string;
		  }
		}
		list link-id {
			leaf link-id {
				type string;
			}
		}
  }
  
	rpc load-topology {
		output {
		  list topology {
					key topology-id;
					leaf topology-id {
						type string;
					}
				}
		}
	}
	
	rpc query-topology {
		input {
			leaf topology-id {
			  type string;
		  }
		}
		output {
		  uses topology;
		}
	}

	rpc query-node {
		input {
		    leaf topology-id {
			    type string;
		    }
				leaf-list node {
				  type string;  
				}
		}
		output {
				list node {
					key node-id;
					uses bier-topology:bier-node;
				}
		}
	}
	
	rpc query-link {
		input {
		    leaf topology-id {
			    type string; 
		    }
				leaf-list link {
				  type string;  
				}
		}
		output {
				list link {
					key link-id;
					uses bier-topology:bier-link;
				}
		}
	}
	
	rpc configure-domain {
		input {
		    leaf topology-id {
			    type string; 
		    }
		    leaf-list domain {
		      type bier-common:domain-id;
		    } 
		}
		output {
        uses bier-common:configure-result;
		}
	}
	
	rpc configure-subdomain {
		input {
		    leaf topology-id {
			    type string; 
		    }
		    leaf domain-id {
			    type bier-common:domain-id; 
		    }
		    
		    leaf-list sub-domain {
		      type bier:sub-domain-id;
		    }
		    
		}
		output {
       uses bier-common:configure-result;
		}
	}								
	
	rpc configure-node {
		input {
		    leaf topology-id {
			    type string; 
		    }
				leaf node-id {
			    type string; 
		    }
		    
		    uses bier-topology:bier-node-params;
		}
		output {
       uses bier-common:configure-result;
		}
	}
	
	rpc query-domain	{
	  input {
		    leaf topology-id {
			    type string; 
		    }
		}
		output {
				list domain {
           leaf domain-id {
             type bier-common:domain-id;
           }
       }
		}	
	}
	
	rpc query-subdomain	{
	  input {
		    leaf topology-id {
			    type string;
		    }
		    leaf domain-id {
			    type bier-common:domain-id; 
		    }
		}
		output {
				list subdomain {
           leaf sub-domain-id {
             type bier:sub-domain-id;
           }
       }
		}	
	}
	
	rpc query-subdomain-node	{
	  input {
		    leaf topology-id {
			    type string;
		    }
		    leaf domain-id {
			    type bier-common:domain-id; 
		    }
		    leaf sub-domain-id {
			    type bier:sub-domain-id;
		    }
		}
		output {
				list subdomain-node {
           uses bier-topology:bier-node;
       }
		}	
	}
	
	rpc query-subdomain-link	{
	  input {
		    leaf topology-id {
			    type string;
		    }
		    leaf domain-id {
			    type bier-common:domain-id; 
		    }
		    leaf sub-domain-id {
			    type bier:sub-domain-id;
		    }
		}
		output {
				list subdomain-link {
           uses bier-topology:bier-link;
       }
		}	
	}
	
	rpc delete-domain	{
	input {
		    leaf topology-id {
			    type string; 
		    }
		     leaf domain-id {
			    type bier-common:domain-id; 
		    }
		}
		output {
       uses bier-common:configure-result;
		}	
	}
	
	rpc delete-subdomain	{
	input {
		    leaf topology-id {
			    type string; 
		    }
		     leaf domain-id {
			    type bier-common:domain-id; 
		    }
		    leaf sub-domain-id {
			    type bier:sub-domain-id;
		    }
		}
		output {
       uses bier-common:configure-result;
		}	
	}
	
	rpc delete-node	{
	  input {
		    leaf topology-id {
			    type string; 
		    }
		     leaf domain-id {
			    type bier-common:domain-id; 
		    }
		    leaf sub-domain-id {
			    type bier:sub-domain-id;
		    }
		    leaf node-id {
			    type string;
		    }
		}
		output {
        uses bier-common:configure-result;
		}	
	}
	
	rpc delete-ipv4	{
	  input {
		    leaf topology-id {
			    type string; 
		    }
		     leaf domain-id {
			    type bier-common:domain-id; 
		    }
		    leaf sub-domain-id {
			    type bier:sub-domain-id;
		    }
		    leaf node-id {
			    type string;
		    }
		    container ipv4 {
			    uses bier:bier-mpls-cfg;
		    }
		}
		output {
        uses bier-common:configure-result;
		}	
	}
	
	rpc delete-ipv6	{
	  input {
		    leaf topology-id {
			    type string; 
		    }
		     leaf domain-id {
			    type bier-common:domain-id; 
		    }
		    leaf sub-domain-id {
			    type bier:sub-domain-id;
		    }
		    leaf node-id {
			    type string;
		    }
		    container ipv6 {
			    uses bier:bier-mpls-cfg;
		    }
		}
		output {
        uses bier-common:configure-result;
		}	
	}
	
	notification topo-change {
        leaf topo-id {
            type string;
        }
	}

	rpc test-notification-publish {
	}
}
