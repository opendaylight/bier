module bier-channel-api {
	namespace "urn:bier:channel:api";
	prefix "bier-channel-api";

  import ietf-bier {
        prefix bier;
    }
  import bier-common {
      prefix bier-common;
  }
  import bier-channel {
      prefix bier-channel;
  }
  
	organization "zte";	
	revision 2016-11-02 {
    description "Initial revision.";
  }
  	
 rpc get-channel {
		input {
			leaf topology-id {
			  type string;
		    }
		}
		output {
		    list channel-name {
                key name;
                leaf name {
                    type string;
                }
            }
		}
	}
	
 rpc query-channel {
		input {
		    leaf topology-id {
			    type string;
		    }
            leaf-list channel-name {
                type string;
            }
		}
		output {
				list channel {
					key name;
					uses bier-channel:channel;
					leaf bier-forwarding-type {
                        type bier-channel:bier-forwarding-type;
                    }
					leaf ingress-node {
                        type string;
                    }
                    leaf src-tp {
                        type string;
                    }
                    list egress-node {
                        leaf node-id {
                          type string;
                        }
                        list rcv-tp {
                            leaf tp {
                                type string;
                            }
                        }
                    }
				}
		}
	}
			
	rpc add-channel {
		input {
		  leaf topology-id {
			  type string;
		  }
		uses bier-channel:channel;
		}
		output {
           uses bier-common:configure-result;
		}
	}
	
	rpc remove-channel {
		input {
			leaf topology-id {
			  type string;
		  }
		  leaf channel-name {
			  type string;
		  }
		}
		output {
           uses bier-common:configure-result;
		}
	}
	
	rpc modify-channel {
		input {
		  leaf topology-id {
			  type string;
		  }
		  uses bier-channel:channel;
		}
		output {
           uses bier-common:configure-result;
		}
	}
	
	rpc deploy-channel {
		input {
		  leaf topology-id {
			  type string;
		  }
		  leaf channel-name {
			  type string;
		  }
			leaf ingress-node {
			  type string;
		  }
		  leaf src-tp {
		      type string;
		  }
		  list egress-node {
			  leaf node-id {
			      type string;
			  }
			  list rcv-tp {
                  leaf tp {
                      type string;
                  }
			  }
		  }
		  leaf bier-forwarding-type {
		      type bier-channel:bier-forwarding-type;
		  }
		  leaf bp-assignment-strategy {
		      type bier-channel:bp-assignment-strategy;
		  }
		}
		output {
           uses bier-common:configure-result;
		}
	}

	rpc query-channel-with-port {
	    input {
            leaf domain-id {
              type bier-common:domain-id;
            }

            leaf sub-domain-id {
              type bier:sub-domain-id;
            }
	        leaf node-id {
	            type string;
	        }
	        leaf tp-id {
	            type string;
	        }

	    }

        output {
            list query-channel {
                leaf channel-name {
                    type string;
                }
                leaf bfir {
                    type string;
                }
                leaf is-rcv-tp {
                    type boolean;
                }
            }
        }
	}

}
